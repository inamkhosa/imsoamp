-- *************************************************************************************
-- PM-CSCF-IMS-MIB:  Performance Management Call State Control Function 
--
-- IP Multimedia Subsystems Management Information
--
-- July 2008, Muhammad Zeeshan
--
-- Copyright (c) 2008-2012 by Adv. IMS, Inc.
--
-- All rights reserved.
-- 
-- *************************************************************************************
--

PM-CSCF-IMS-MIB DEFINITIONS ::= BEGIN

--
-- Performance Management CSCF MIB for IMS project
--

IMPORTS
    MODULE-IDENTITY, OBJECT-TYPE, Integer32, Counter32	FROM SNMPv2-SMI
        TruthValue, TestAndIncr              		FROM SNMPv2-TC
    pManagement 					FROM PM-IMS-MIB;


pMngtCSCF MODULE-IDENTITY
    LAST-UPDATED "200807070000Z"
    ORGANIZATION "www.advancedims.com"
    CONTACT-INFO    
	 "postal:   Muhammad Zeeshan
		    Advanced IP Multimedia Subsystems
                    House # 299, Street # 67
                    Islamabad, Pakistan.

          email:    m.zeeshan@advancedims.com"
    DESCRIPTION
	"CSCF MIB for the Performance Management - Advanced IMS project enterprise MIB tree"
    REVISION     "200807070000Z"
    DESCRIPTION
	"First draft"
    ::= { pManagement 1 }


--
-- top level object identifiers for CSCF regarding Performance Management
--

--Requirement # 11
interNetwrokSessionAttempt OBJECT-TYPE
    SYNTAX      Integer32
    MAX-ACCESS  read-write
    STATUS      current
    DESCRIPTION
	"This is an object for inter network session attempts."
    DEFVAL { 0 }
    ::= { pMngtCSCF 1 }


--Requirement # 11
interNetwrokSessionForbidden OBJECT-TYPE
    SYNTAX      Integer32
    MAX-ACCESS  read-write
    STATUS      current
    DESCRIPTION
	"This is an object for inter network session forbidden."
    DEFVAL { 0 }
    ::= { pMngtCSCF 2 }

--Requirement # 12
regProcedureAttempt OBJECT-TYPE
    SYNTAX      Integer32
    MAX-ACCESS  read-write
    STATUS      current
    DESCRIPTION
	"This is an object for registration procedure attempts."
    DEFVAL { 0 }
    ::= { pMngtCSCF 3 }

--Requirement # 12
regProcedureSuccess OBJECT-TYPE
    SYNTAX      Integer32
    MAX-ACCESS  read-write
    STATUS      current
    DESCRIPTION
	"This is an object for registration procedure success."
    DEFVAL { 0 }
    ::= { pMngtCSCF 4 }

--Requirement # 12
regProcedureFailed OBJECT-TYPE
    SYNTAX      Integer32
    MAX-ACCESS  read-write
    STATUS      current
    DESCRIPTION
	"This is an object for registration procedure failed."
    DEFVAL { 0 }
    ::= { pMngtCSCF 5 }

--Requirement # 12
authProcedureAttempt OBJECT-TYPE
    SYNTAX      Integer32
    MAX-ACCESS  read-write
    STATUS      current
    DESCRIPTION
	"This is an object for authantication procedure attempts."
    DEFVAL { 0 }
    ::= { pMngtCSCF 6 }

--Requirement # 12
authProcedureSuccess OBJECT-TYPE
    SYNTAX      Integer32
    MAX-ACCESS  read-write
    STATUS      current
    DESCRIPTION
	"This is an object for authantication procedure success."
    DEFVAL { 0 }
    ::= { pMngtCSCF 7 }

--Requirement # 12
authProcedureFailed OBJECT-TYPE
    SYNTAX      Integer32
    MAX-ACCESS  read-write
    STATUS      current
    DESCRIPTION
	"This is an object for authantication procedure failed."
    DEFVAL { 0 }
    ::= { pMngtCSCF 8 }

--Requirement # 13
tcpSessionAttempt OBJECT-TYPE
    SYNTAX      Integer32
    MAX-ACCESS  read-only
    STATUS      current
    DESCRIPTION
	"This is an object for TCP sessions attempts."
    DEFVAL { 0 }
    ::= { pMngtCSCF 9 }

--Requirement # 13
tcpSessionSuccess OBJECT-TYPE
    SYNTAX      Integer32
    MAX-ACCESS  read-write
    STATUS      current
    DESCRIPTION
	"This is an object for TCP sessions success."
    DEFVAL { 0 }
    ::= { pMngtCSCF 10 }

--Requirement # 13
tcpSessionFailed OBJECT-TYPE
    SYNTAX      Integer32
    MAX-ACCESS  read-write
    STATUS      current
    DESCRIPTION
	"This is an object for TCP sessions failed."
    DEFVAL { 0 }
    ::= { pMngtCSCF 11 }

--Requirement # 13
sctpSessionAttempt OBJECT-TYPE
    SYNTAX      Integer32
    MAX-ACCESS  read-write
    STATUS      current
    DESCRIPTION
	"This is an object for STCP sessions attempts."
    DEFVAL { 0 }
    ::= { pMngtCSCF 12 }

--Requirement # 13
sctpSessionSuccess OBJECT-TYPE
    SYNTAX      Integer32
    MAX-ACCESS  read-write
    STATUS      current
    DESCRIPTION
	"This is an object for STCP sessions success."
    DEFVAL { 0 }
    ::= { pMngtCSCF 13 }

--Requirement # 13
sctpSessionFailed OBJECT-TYPE
    SYNTAX      Integer32
    MAX-ACCESS  read-write
    STATUS      current
    DESCRIPTION
	"This is an object for STCP sessions failed."
    DEFVAL { 0 }
    ::= { pMngtCSCF 14 }

END

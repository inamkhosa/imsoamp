-- *************************************************************************************
-- MISC-ELEMENT-MANAGER-IMS-MIB: MISC Element Manager  MIB
--
-- IP Multimedia Subsystems Management Information
--
-- January 2009, Muhammad Zeeshan
--
-- Copyright (c) 2008-2012 by Adv. IMS, Inc.
--
-- All rights reserved.
-- 
-- *************************************************************************************
--

MISC-ELEMENT-MANAGER-IMS-MIB DEFINITIONS ::= BEGIN

--
-- Misc OIDs for Element Manager MIB for IMS project
--

IMPORTS
    MODULE-IDENTITY, OBJECT-TYPE, Integer32 FROM SNMPv2-SMI
        TruthValue, TestAndIncr              FROM SNMPv2-TC
    elementManager 			FROM ELEMENT-MANAGER-IMS-MIB;


elementMiscOIDs MODULE-IDENTITY
    LAST-UPDATED "200801180000Z"
    ORGANIZATION "www.advancedims.com"
    CONTACT-INFO    
	 "postal:   Muhammad Zeeshan
		    Advanced IP Multimedia Subsystems
                    House # 299, Street # 67
                    Islamabad, Pakistan.

          email:    m.zeeshan@advancedims.com"
    DESCRIPTION
	"Misc OIDs for Element Manager - Advanced IMS project enterprise MIB tree."
    REVISION     "200801180000Z"
    DESCRIPTION
	"First draft"
    ::= { elementManager 1 }



--
--  Misc OIDs for Element Manager
--

elementStatus		OBJECT-TYPE
    SYNTAX      Integer32
    MAX-ACCESS  read-write
    STATUS      current
    DESCRIPTION
	"This is an object for no of invite messages received."
    DEFVAL { 0 }
    ::= { elementMiscOIDs 1 }

END
